# -*- coding: utf-8 -*-
import FreeCAD as App, FreeCADGui as Gui, Part, math

DOC_NAME = "Ship_Solid_Unified"
if App.ActiveDocument is None or App.ActiveDocument.Label != DOC_NAME:
    App.newDocument(DOC_NAME)
doc = App.ActiveDocument

P = {
    "nose_len": 800.0, "nose_base_d": 1100.0, "nose_cap_d": 520.0,
    "mid_len": 2300.0, "mid_d": 1800.0,
    "rear_len": 1700.0, "rear_d": 2200.0,
    "cockpit_w": 980.0, "cockpit_h": 520.0, "cockpit_l": 860.0,
    "cockpit_x0": 620.0, "cockpit_blend_r": 120.0,
    "reactor_d": 1500.0, "reactor_l": 2100.0, "reactor_cx": 3400.0,
    "nozzle_throat_d": 520.0, "nozzle_exit_d": 2000.0,
    "nozzle_l": 1900.0, "nozzle_cx": 4500.0,
    "booster_n": 4, "booster_d": 900.0, "booster_l": 1650.0,
    "booster_ring_r": 1650.0, "booster_nozzle_d": 620.0, "booster_nozzle_l": 420.0,
    "wing_root_w": 1300.0, "wing_tip_w": 320.0, "wing_chord": 650.0,
    "wing_sweep_deg": 27.0,
    "tank_r": 420.0, "tank_l": 2100.0, "tank_off": 1300.0,
    "sphere_r": 480.0, "sphere_off": 1700.0,
    "mast_l": 1100.0, "mast_r": 44.0, "dish_r": 420.0,
    "leg_r": 110.0, "leg_l": 880.0, "foot_r": 280.0, "foot_t": 55.0,
}

def rot_to_x(): return App.Rotation(App.Vector(0,1,0),90)

# -----------------------------
# Nariz con loft sólido
# -----------------------------
def make_nose():
    radii = [P["nose_base_d"]/2.0, 450.0, 260.0, P["nose_cap_d"]/2.0]
    xpos  = [0, P["nose_len"]*0.35, P["nose_len"]*0.7, P["nose_len"]]
    sections = [Part.makeCircle(r, App.Vector(x,0,0), App.Vector(1,0,0)) for r,x in zip(radii,xpos)]
    return Part.makeLoft(sections, True)

# -----------------------------
# Fuselaje medio y trasero
# -----------------------------
def make_body():
    mid = Part.makeCylinder(P["mid_d"]/2.0, P["mid_len"])
    mid.Placement = App.Placement(App.Vector(P["nose_len"],0,0), rot_to_x())
    rear = Part.makeCylinder(P["rear_d"]/2.0, P["rear_len"])
    rear.Placement = App.Placement(App.Vector(P["nose_len"]+P["mid_len"],0,0), rot_to_x())
    return mid.fuse(rear)

# -----------------------------
# Cockpit integrado
# -----------------------------
def make_cockpit():
    box = Part.makeBox(P["cockpit_l"], P["cockpit_w"], P["cockpit_h"])
    box.Placement = App.Placement(App.Vector(P["cockpit_x0"],-P["cockpit_w"]/2.0,-P["cockpit_h"]/2.0),App.Rotation())
    sphere = Part.makeSphere(P["cockpit_blend_r"])
    sphere.Placement = App.Placement(App.Vector(P["cockpit_x0"]-P["cockpit_blend_r"]/2.0,0,0),App.Rotation())
    return box.fuse(sphere)

# -----------------------------
# Reactor + boquilla
# -----------------------------
def make_reactor():
    core = Part.makeCylinder(P["reactor_d"]/2.0, P["reactor_l"])
    core.Placement = App.Placement(App.Vector(P["reactor_cx"]-P["reactor_l"]/2.0,0,0), rot_to_x())
    throat = Part.makeCylinder(P["nozzle_throat_d"]/2.0, 260.0)
    throat.Placement = App.Placement(App.Vector(P["nozzle_cx"]-P["nozzle_l"]/2.0-130.0,0,0), rot_to_x())
    cone = Part.makeCone(P["nozzle_throat_d"]/2.0, P["nozzle_exit_d"]/2.0, P["nozzle_l"])
    cone.Placement = App.Placement(App.Vector(P["nozzle_cx"]-P["nozzle_l"]/2.0,0,0), rot_to_x())
    return core.fuse(throat).fuse(cone)

# -----------------------------
# Boosters radiales
# -----------------------------
def make_boosters():
    boosters=[]
    base_x = P["nose_len"]+P["mid_len"]+P["rear_len"]-P["booster_l"]*0.6
    for k in range(P["booster_n"]):
        ang=k*(360.0/P["booster_n"])
        y=P["booster_ring_r"]*math.cos(math.radians(ang))
        z=P["booster_ring_r"]*math.sin(math.radians(ang))
        cyl=Part.makeCylinder(P["booster_d"]/2.0,P["booster_l"])
        cyl.Placement=App.Placement(App.Vector(base_x, y, z), rot_to_x())
        noz=Part.makeCone(P["booster_nozzle_d"]/2.0,P["booster_nozzle_d"]/4.0,P["booster_nozzle_l"])
        noz.Placement=App.Placement(App.Vector(base_x+P["booster_l"],y,z),rot_to_x())
        boosters.append(cyl.fuse(noz))
    u=boosters[0]
    for b in boosters[1:]: u=u.fuse(b)
    return u

# -----------------------------
# Alas trapezoidales
# -----------------------------
def make_wings():
    wings=[]
    for side in [1,-1]:
        root=P["wing_root_w"]; tip=P["wing_tip_w"]; chord=P["wing_chord"]; sweep=P["wing_sweep_deg"]
        x0=P["nose_len"]+900; x1=x0+chord; z=0
        p1=App.Vector(x0,0,z+root/2.0); p2=App.Vector(x1,0,z+tip/2.0)
        p3=App.Vector(x1,0,z-tip/2.0); p4=App.Vector(x0,0,z-root/2.0)
        wire=Part.makePolygon([p1,p2,p3,p4,p1]); face=Part.Face(wire)
        solid=face.extrude(App.Vector(0,side*(root-tip),0))
        wings.append(solid)
    return wings[0].fuse(wings[1])

# -----------------------------
# Tanques y esferas
# -----------------------------
def make_tanks():
    tL=Part.makeCylinder(P["tank_r"],P["tank_l"])
    tL.Placement=App.Placement(App.Vector(P["nose_len"]+1100,P["tank_off"],0),rot_to_x())
    tR=Part.makeCylinder(P["tank_r"],P["tank_l"])
    tR.Placement=App.Placement(App.Vector(P["nose_len"]+1100,-P["tank_off"],0),rot_to_x())
    sL=Part.makeSphere(P["sphere_r"])
    sL.Placement=App.Placement(App.Vector(P["nose_len"]+2600,P["sphere_off"],0),App.Rotation())
    sR=Part.makeSphere(P["sphere_r"])
    sR.Placement=App.Placement(App.Vector(P["nose_len"]+2600,-P["sphere_off"],0),App.Rotation())
    return tL.fuse(tR).fuse(sL).fuse(sR)

# -----------------------------
# Antena (mástil + plato)
# -----------------------------
def make_antenna():
    mast = Part.makeCylinder(P["mast_r"], P["mast_l"])
    mast.Placement = App.Placement(App.Vector(P["nose_len"]+P["mid_len"], P["mid_d"]/2.0+130.0, 0), rot_to_x())
    dish = Part.makeSphere(P["dish_r"])
    # Aplano el plato para simular antena parabólica
    try:
        dish.Placement.Scale = App.Vector(1,1,0.3)
    except:
        pass
    dish.Placement = App.Placement(App.Vector(P["nose_len"]+P["mid_len"]+P["mast_l"], P["mid_d"]/2.0+130.0, 0), App.Rotation())
    return mast.fuse(dish)

# -----------------------------
# Tren de aterrizaje radial
# -----------------------------
def make_landing_gear():
    legs=[]
    for angle in [0,90,180,270]:
        leg = Part.makeCylinder(P["leg_r"], P["leg_l"])
        lx = (P["mid_d"]/2.0 - 90.0)*math.cos(math.radians(angle))
        lz = (P["mid_d"]/2.0 - 90.0)*math.sin(math.radians(angle))
        leg.Placement = App.Placement(App.Vector(P["nose_len"]-180.0, lx, lz), rot_to_x())
        foot = Part.makeCylinder(P["foot_r"], P["foot_t"])
        foot.Placement = App.Placement(App.Vector(P["nose_len"]-180.0+P["leg_l"], lx, lz), rot_to_x())
        legs.append(leg.fuse(foot))
    u = legs[0]
    for l in legs[1:]:
        u = u.fuse(l)
    return u

# -----------------------------
# Ensamblaje completo
# -----------------------------
nose = make_nose()
body = make_body()
cockpit = make_cockpit()
reactor = make_reactor()
boosters = make_boosters()
wings = make_wings()
tanks = make_tanks()
antenna = make_antenna()
landing = make_landing_gear()

# Fusión global de todos los subsistemas
ship = nose.fuse(body)
for part in [cockpit, reactor, boosters, wings, tanks, antenna, landing]:
    ship = ship.fuse(part)

# Crear objeto final en FreeCAD
ship_obj = doc.addObject("Part::Feature", "Ship_Solid_Unified")
ship_obj.Shape = ship
ship_obj.ViewObject.ShapeColor = (0.72,0.72,0.74)
ship_obj.ViewObject.DisplayMode = "Shaded"

doc.recompute()

try:
    Gui.ActiveDocument.ActiveView.viewAxonometric()
    Gui.SendMsgToActiveView("ViewFit")
except:
    pass

print("Macro 'Ship_Solid_Unified' lista en '{}'.".format(doc.Label))
